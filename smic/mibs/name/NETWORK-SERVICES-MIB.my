-- file: NETWORK-SERVICES-MIB.my (RFC 2248)
-- Changes: 
--      Updated formatting of quoted text.
--      Added REVISION clause to MODULE-IDENTITY to describe changes. 
--      Added copyright to MODULE-IDENTITY description.
--
-- Problems:
--      1) object applDirectoryName must be contained in at least
--         one object group
--      2) Enum values ua-initiator, ua-responder, peer-initiator,
--         and peer-responder contain dashes, which is technically
--         illegal, but practically ignored
--      3) Objects applDescription and applURL were illegally added
--         to object group applGroup. (After you publish an RFC,
--         you can not change the members of an object group.)
--
-- dperkins@snmpinfo.com: 18-apr-1998


NETWORK-SERVICES-MIB DEFINITIONS ::= BEGIN

IMPORTS
    OBJECT-TYPE, Counter32, Gauge32, MODULE-IDENTITY, mib-2
      FROM SNMPv2-SMI
    DisplayString, TimeStamp, TEXTUAL-CONVENTION
      FROM SNMPv2-TC
    MODULE-COMPLIANCE, OBJECT-GROUP
      FROM SNMPv2-CONF;

application MODULE-IDENTITY
    LAST-UPDATED "9708170000Z"
    ORGANIZATION "IETF Mail and Directory Management Working Group"
    CONTACT-INFO
      "        Ned Freed

       Postal: Innosoft International, Inc.
               1050 Lakes Drive
               West Covina, CA 91790
               US

          Tel: +1 626 919 3600
          Fax: +1 626 919 3614

       E-Mail: ned.freed@innosoft.com"
    DESCRIPTION
      "The MIB module describing network service applications

   Copyright (C) The Internet Society (1998). All Rights Reserved.

   This document and translations of it may be copied and furnished to
   others, and derivative works that comment on or otherwise explain it
   or assist in its implementation may be prepared, copied, published
   and distributed, in whole or in part, without restriction of any
   kind, provided that the above copyright notice and this paragraph
   are included on all such copies and derivative works.  However, this
   document itself may not be modified in any way, such as by removing
   the copyright notice or references to the Internet Society or other
   Internet organizations, except as needed for the purpose of
   developing Internet standards in which case the procedures for
   copyrights defined in the Internet Standards process must be
   followed, or as required to translate it into languages other than
   English.

   The limited permissions granted above are perpetual and will not be
   revoked by the Internet Society or its successors or assigns.

   This document and the information contained herein is provided on an
   'AS IS' basis and THE INTERNET SOCIETY AND THE INTERNET ENGINEERING
   TASK FORCE DISCLAIMS ALL WARRANTIES, EXPRESS OR IMPLIED, INCLUDING
   BUT NOT LIMITED TO ANY WARRANTY THAT THE USE OF THE INFORMATION
   HEREIN WILL NOT INFRINGE ANY RIGHTS OR ANY IMPLIED WARRANTIES OF
   MERCHANTABILITY OR FITNESS FOR A PARTICULAR PURPOSE."

    REVISION "9708170000Z"
        DESCRIPTION
            "Published in RFC 2248 with the following changes:
              - Added enum value quiescing(6) to object applOperStatus.
              - Added objects applDescription and applURL
              - Added TC URLString
              - **Illegally added objects applDescription and applURL
                  to object group applGroup**
              - Changed module name from APPLICATION-MIB to
                  NETWORK-SERVICES-MIB"
    REVISION "9311280000Z"
        DESCRIPTION
            "The initial version of this MIB module was published
            in RFC 1565."
    ::= {mib-2 27}

-- Textual conventions

-- DistinguishedName is used to refer to objects in the
-- directory.

DistinguishedName ::= TEXTUAL-CONVENTION
    STATUS current
    DESCRIPTION
        "A Distinguished Name represented in accordance with
        RFC 1779 [8]."
    SYNTAX DisplayString

-- Uniform Resource Locators are stored in URLStrings.

URLString ::= TEXTUAL-CONVENTION
    STATUS current
    DESCRIPTION
        "A Uniform Resource Locator represented in accordance
        with RFC 1738 [10]."
    SYNTAX DisplayString

-- The basic applTable contains a list of the application
-- entities.

applTable OBJECT-TYPE
    SYNTAX SEQUENCE OF ApplEntry
    MAX-ACCESS not-accessible
    STATUS current
    DESCRIPTION
        "The table holding objects which apply to all different
        kinds of applications providing network services.
        Each network service application capable of being
        monitored should have a single entry in this table."
    ::= {application 1}

applEntry OBJECT-TYPE
    SYNTAX ApplEntry
    MAX-ACCESS not-accessible
    STATUS current
    DESCRIPTION
        "An entry associated with a single network service
        application."
    INDEX {applIndex}
    ::= {applTable 1}

ApplEntry ::= SEQUENCE {
    applIndex
        INTEGER,
    applName
        DisplayString,
    applDirectoryName
        DistinguishedName,
    applVersion
        DisplayString,
    applUptime
        TimeStamp,
    applOperStatus
        INTEGER,
    applLastChange
        TimeStamp,
    applInboundAssociations
        Gauge32,
    applOutboundAssociations
        Gauge32,
    applAccumulatedInboundAssociations
        Counter32,
    applAccumulatedOutboundAssociations
        Counter32,
    applLastInboundActivity
        TimeStamp,
    applLastOutboundActivity
        TimeStamp,
    applRejectedInboundAssociations
        Counter32,
    applFailedOutboundAssociations
        Counter32,
    applDescription
        DisplayString,
    applURL
        URLString
}

applIndex OBJECT-TYPE
    SYNTAX INTEGER (1..2147483647)
    MAX-ACCESS not-accessible
    STATUS current
    DESCRIPTION
        "An index to uniquely identify the network service
        application. This attribute is the index used for
        lexicographic ordering of the table."
    ::= {applEntry 1}

applName OBJECT-TYPE
    SYNTAX DisplayString
    MAX-ACCESS read-only
    STATUS current
    DESCRIPTION
        "The name the network service application chooses to be
        known by."
    ::= {applEntry 2}

applDirectoryName OBJECT-TYPE
    SYNTAX DistinguishedName
    MAX-ACCESS read-only
    STATUS current
    DESCRIPTION
        "The Distinguished Name of the directory entry where
        static information about this application is stored.
        An empty string indicates that no information about
        the application is available in the directory."
    ::= {applEntry 3}

applVersion OBJECT-TYPE
    SYNTAX DisplayString
    MAX-ACCESS read-only
    STATUS current
    DESCRIPTION
        "The version of network service application software.
        This field is usually defined by the vendor of the
        network service application software."
    ::= {applEntry 4}

applUptime OBJECT-TYPE
    SYNTAX TimeStamp
    MAX-ACCESS read-only
    STATUS current
    DESCRIPTION
        "The value of sysUpTime at the time the network service
        application was last initialized.  If the application was
        last initialized prior to the last initialization of the
        network management subsystem, then this object contains
        a zero value."
    ::= {applEntry 5}

applOperStatus OBJECT-TYPE
    SYNTAX INTEGER {
      up(1),
      down(2),
      halted(3),
      congested(4),
      restarting(5),
      quiescing(6)
    }
    MAX-ACCESS read-only
    STATUS current
    DESCRIPTION
        "Indicates the operational status of the network service
        application. 'down' indicates that the network service is
        not available. 'up' indicates that the network service
        is operational and available.  'halted' indicates that the
        service is operational but not available.  'congested'
        indicates that the service is operational but no additional
        inbound associations can be accomodated.  'restarting'
        indicates that the service is currently unavailable but is
        in the process of restarting and will be available soon.
        'quiescing' indicates that service is currently operational
        but is in the process of shutting down. Additional inbound
        associations may be rejected by applications in the
        'quiescing' state."
    ::= {applEntry 6}

applLastChange OBJECT-TYPE
    SYNTAX TimeStamp
    MAX-ACCESS read-only
    STATUS current
    DESCRIPTION
        "The value of sysUpTime at the time the network service
        application entered its current operational state.  If
        the current state was entered prior to the last
        initialization of the local network management subsystem,
        then this object contains a zero value."
    ::= {applEntry 7}

applInboundAssociations OBJECT-TYPE
    SYNTAX Gauge32
    MAX-ACCESS read-only
    STATUS current
    DESCRIPTION
        "The number of current associations to the network service
        application, where it is the responder.  An inbound
        assocation occurs when a another application successfully
        connects to this one."
    ::= {applEntry 8}

applOutboundAssociations OBJECT-TYPE
    SYNTAX Gauge32
    MAX-ACCESS read-only
    STATUS current
    DESCRIPTION
        "The number of current associations to the network service
        application, where it is the initiator.  An outbound
        association occurs when this application successfully
        connects to another one."
    ::= {applEntry 9}

applAccumulatedInboundAssociations OBJECT-TYPE
    SYNTAX Counter32
    MAX-ACCESS read-only
    STATUS current
    DESCRIPTION
        "The total number of associations to the application entity
        since application initialization, where it was the responder."
    ::= {applEntry 10}

applAccumulatedOutboundAssociations OBJECT-TYPE
    SYNTAX Counter32
    MAX-ACCESS read-only
    STATUS current
    DESCRIPTION
        "The total number of associations to the application entity
        since application initialization, where it was the initiator."
    ::= {applEntry 11}

applLastInboundActivity OBJECT-TYPE
    SYNTAX TimeStamp
    MAX-ACCESS read-only
    STATUS current
    DESCRIPTION
        "The value of sysUpTime at the time this application last
        had an inbound association.  If the last association
        occurred prior to the last initialization of the network
        subsystem, then this object contains a zero value."
    ::= {applEntry 12}

applLastOutboundActivity OBJECT-TYPE
    SYNTAX TimeStamp
    MAX-ACCESS read-only
    STATUS current
    DESCRIPTION
        "The value of sysUpTime at the time this application last
        had an outbound association.  If the last association
        occurred prior to the last initialization of the network
        subsystem, then this object contains a zero value."
    ::= {applEntry 13}

applRejectedInboundAssociations OBJECT-TYPE
    SYNTAX Counter32
    MAX-ACCESS read-only
    STATUS current
    DESCRIPTION
        "The total number of inbound associations the application
        entity has rejected, since application initialization.
        Rejected associations are not counted in the accumulated
        association totals.  Note that this only counts
        associations the application entity has rejected itself;
        it does not count rejections that occur at lower layers
        of the network.  Thus, this counter may not reflect the
        true number of failed inbound associations."
    ::= {applEntry 14}

applFailedOutboundAssociations OBJECT-TYPE
    SYNTAX Counter32
    MAX-ACCESS read-only
    STATUS current
    DESCRIPTION
        "The total number associations where the application entity
        is initiator and association establishment has failed,
        since application initialization.  Failed associations are
        not counted in the accumulated association totals."
    ::= {applEntry 15}

applDescription OBJECT-TYPE
    SYNTAX DisplayString
    MAX-ACCESS read-only
    STATUS current
    DESCRIPTION
        "A text description of the application.  This information
        is intended to identify and briefly describe the
        application in a status display."
    ::= {applEntry 16}

applURL OBJECT-TYPE
    SYNTAX URLString
    MAX-ACCESS read-only
    STATUS current
    DESCRIPTION
        "A URL pointing to a description of the application.
        This information is intended to identify and describe
        the application in a status display."
    ::= {applEntry 17}


-- The assocTable augments the information in the applTable
-- with information about associations.  Note that two levels
-- of compliance are specified below, depending on whether
-- association monitoring is mandated.

assocTable OBJECT-TYPE
    SYNTAX SEQUENCE OF AssocEntry
    MAX-ACCESS not-accessible
    STATUS current
    DESCRIPTION
        "The table holding a set of all active application
        associations."
    ::= {application 2}

assocEntry OBJECT-TYPE
    SYNTAX AssocEntry
    MAX-ACCESS not-accessible
    STATUS current
    DESCRIPTION
        "An entry associated with an association for a network
        service application."
    INDEX {applIndex, assocIndex}
    ::= {assocTable 1}

AssocEntry ::= SEQUENCE {
    assocIndex
        INTEGER,
    assocRemoteApplication
        DisplayString,
    assocApplicationProtocol
        OBJECT IDENTIFIER,
    assocApplicationType
        INTEGER,
    assocDuration
        TimeStamp
}

assocIndex OBJECT-TYPE
    SYNTAX INTEGER (1..2147483647)
    MAX-ACCESS not-accessible
    STATUS current
    DESCRIPTION
        "An index to uniquely identify each association for a network
        service application.  This attribute is the index that is
        used for lexicographic ordering of the table.  Note that the
        table is also indexed by the applIndex."
    ::= {assocEntry 1}

assocRemoteApplication OBJECT-TYPE
    SYNTAX DisplayString
    MAX-ACCESS read-only
    STATUS current
    DESCRIPTION
        "The name of the system running remote network service
        application.  For an IP-based application this should be
        either a domain name or IP address.  For an OSI application
        it should be the string encoded distinguished name of the
        managed object.  For X.400(1984) MTAs which do not have a
        Distinguished Name, the RFC 1327 [9] syntax
        'mta in globalid' should be used. Note, however, that not
        all connections an MTA are necessarily to another MTA."
    ::= {assocEntry 2}

assocApplicationProtocol OBJECT-TYPE
    SYNTAX OBJECT IDENTIFIER
    MAX-ACCESS read-only
    STATUS current
    DESCRIPTION
        "An identification of the protocol being used for the
        application.  For an OSI Application, this will be the
        Application Context.  For Internet applications, the IANA
        maintains a registry of the OIDs which correspond to
        well-known applications.  If the application protocol is
        not listed in the registry, an OID value of the form
        {applTCPProtoID port} or {applUDProtoID port} are used for
        TCP-based and UDP-based protocols, respectively. In either
        case 'port' corresponds to the primary port number being
        used by the protocol."
    ::= {assocEntry 3}

assocApplicationType OBJECT-TYPE
    SYNTAX INTEGER {
        ua-initiator(1),
        ua-responder(2),
        peer-initiator(3),
        peer-responder(4)}
    MAX-ACCESS read-only
    STATUS current
    DESCRIPTION
        "This indicates whether the remote application is some type of
        client making use of this network service (e.g. a Mail User
        Agent) or a server acting as a peer. Also indicated is whether
        the remote end initiated an incoming connection to the network
        service or responded to an outgoing connection made by the
        local application.  MTAs and messaging gateways are
        considered to be peers for the purposes of this variable."
    ::= {assocEntry 4}

assocDuration OBJECT-TYPE
    SYNTAX TimeStamp
    MAX-ACCESS read-only
    STATUS current
    DESCRIPTION
        "The value of sysUpTime at the time this association was
        started.  If this association started prior to the last
        initialization of the network subsystem, then this
        object contains a zero value."
    ::= {assocEntry 5}


-- Conformance information

applConformance OBJECT IDENTIFIER ::= {application 3}

applGroups      OBJECT IDENTIFIER ::= {applConformance 1}
applCompliances OBJECT IDENTIFIER ::= {applConformance 2}


-- Compliance statements

applCompliance MODULE-COMPLIANCE
    STATUS current
    DESCRIPTION
        "The compliance statement for SNMPv2 entities
        which implement the Network Services Monitoring MIB
        for basic monitoring of network service applications."
    MODULE  -- this module
      MANDATORY-GROUPS {applGroup}
    ::= {applCompliances 1}

assocCompliance MODULE-COMPLIANCE
    STATUS current
    DESCRIPTION
        "The compliance statement for SNMPv2 entities which
        implement the Network Services Monitoring MIB for basic
        monitoring of network service applications and their
        associations."
    MODULE  -- this module
      MANDATORY-GROUPS {applGroup, assocGroup}
    ::= {applCompliances 2}


-- Units of conformance

applGroup OBJECT-GROUP
    OBJECTS {
      applName, applVersion, applUptime, applOperStatus,
      applLastChange, applInboundAssociations,
      applOutboundAssociations, applAccumulatedInboundAssociations,
      applAccumulatedOutboundAssociations, applLastInboundActivity,
      applLastOutboundActivity, applRejectedInboundAssociations,
      applFailedOutboundAssociations, applDescription, applURL}
    STATUS current
    DESCRIPTION
        "A collection of objects providing basic monitoring of
        network service applications."
    ::= {applGroups 1}


assocGroup OBJECT-GROUP
    OBJECTS {
      assocRemoteApplication, assocApplicationProtocol,
      assocApplicationType, assocDuration}
    STATUS current
    DESCRIPTION
        "A collection of objects providing basic monitoring of
        network service applications' associations."
    ::= {applGroups 2}


-- OIDs of the form {applTCPProtoID port} are intended to be used
-- for TCP-based protocols that don't have OIDs assigned by other
-- means. {applUDPProtoID port} serves the same purpose for
-- UDP-based protocols. In either case 'port' corresponds to
-- the primary port number being used by the protocol. For example,
-- assuming no other OID is assigned for SMTP, an OID of
-- {applTCPProtoID 25} could be used, since SMTP is a TCP-based
-- protocol that uses port 25 as its primary port.

applTCPProtoID OBJECT IDENTIFIER ::= {application 4}
applUDPProtoID OBJECT IDENTIFIER ::= {application 5}

END
